module acl-rfs {

  namespace "http://ciscolive.com/acl-rfs";
  prefix acl-rfs;

  import ietf-inet-types {
    prefix inet;
  }
  import tailf-common {
    prefix tailf;
  }
  import tailf-ncs {
    prefix ncs;
  }

  description
    "Small rfs package for demonstration purposes";

  revision 2026-02-07 {
    description
      "Added logging flag to the ACL rule";
  }

  revision 2025-02-02 {
    description
      "Awesome NetDevOps demo";
  }

  list access-list-acl-rfs {
    description "Refactoring of rfs service for access lists provisioning on IOSXR devices";
    uses ncs:service-data;
    ncs:servicepoint access-list-acl-rfs-servicepoint;

    key "device";

    leaf device {
      tailf:info "Cisco IOSXR device";
      tailf:cli-expose-key-name;
      type leafref {
        path "/ncs:devices/ncs:device/ncs:name";
      }
      mandatory true;
    }

    list access_list {
      tailf:info "New Access-list";
      key "name";

      leaf name {
        tailf:info "Access-list name";
        type string;
      }

      list rule {
        tailf:info "New rule within the Access-list";
        key "id";

        leaf id {
          tailf:info "rule id";
          type uint32;
        }

        leaf action {
          tailf:info "Access type enumeration";
          type enumeration {
            enum "permit";
            enum "deny";
          }
          mandatory true;
        }

        leaf destination {
          tailf:info "Destination IP address";
          type inet:ipv4-address;
          mandatory true;
        }

        leaf log {
          tailf:info "Logging option";
          type boolean;
          default false;
        }    
      }
    }
  }
}
